[DOCUMENT]
TITLE: NMFTA Telematics (Vehicle Connection Component) Security Requirements

[REQUIREMENT]
UID: VEH-AC-010
REFS:
- TYPE: Parent
  VALUE: AC-010
STATEMENT: >>>
This Vehicle Connection component must satisfy requirement AC-010
<<<

[REQUIREMENT]
UID: VEH-AC-020
REFS:
- TYPE: Parent
  VALUE: AC-020
STATEMENT: >>>
This Vehicle Connection component must satisfy requirement AC-020
<<<

[REQUIREMENT]
UID: VEH-AC-030
REFS:
- TYPE: Parent
  VALUE: AC-030
STATEMENT: >>>
This Vehicle Connection component must satisfy requirement AC-030
<<<

[REQUIREMENT]
UID: VEH-AC-040
REFS:
- TYPE: Parent
  VALUE: AC-040
STATEMENT: >>>
This Vehicle Connection component must satisfy requirement AC-040
<<<

[REQUIREMENT]
UID: VEH-AC-041
REFS:
- TYPE: Parent
  VALUE: AC-041
STATEMENT: >>>
This Vehicle Connection component must satisfy requirement AC-041
<<<

[REQUIREMENT]
UID: VEH-AC-050
REFS:
- TYPE: Parent
  VALUE: AC-050
STATEMENT: >>>
This Vehicle Connection component must satisfy requirement AC-050
<<<

[REQUIREMENT]
UID: VEH-AC-060
REFS:
- TYPE: Parent
  VALUE: AC-060
STATEMENT: >>>
This Vehicle Connection component must satisfy requirement AC-060
<<<

[REQUIREMENT]
UID: VEH-AC-061
REFS:
- TYPE: Parent
  VALUE: AC-061
STATEMENT: >>>
This Vehicle Connection component must satisfy requirement AC-061
<<<

[REQUIREMENT]
UID: VEH-AC-062
REFS:
- TYPE: Parent
  VALUE: AC-062
STATEMENT: >>>
This Vehicle Connection component must satisfy requirement AC-062
<<<

[REQUIREMENT]
UID: VEH-AC-063
REFS:
- TYPE: Parent
  VALUE: AC-063
STATEMENT: >>>
This Vehicle Connection component must satisfy requirement AC-063
<<<

[REQUIREMENT]
UID: VEH-AC-080
REFS:
- TYPE: Parent
  VALUE: AC-080
STATEMENT: >>>
This Vehicle Connection component must satisfy requirement AC-080
<<<

[REQUIREMENT]
UID: VEH-CM-010
REFS:
- TYPE: Parent
  VALUE: CM-010
STATEMENT: >>>
This Vehicle Connection component must satisfy requirement CM-010
<<<

[REQUIREMENT]
UID: VEH-CM-020
REFS:
- TYPE: Parent
  VALUE: CM-020
STATEMENT: >>>
This Vehicle Connection component must satisfy requirement CM-020
<<<

[REQUIREMENT]
UID: VEH-CM-030
REFS:
- TYPE: Parent
  VALUE: CM-030
STATEMENT: >>>
This Vehicle Connection component must satisfy requirement CM-030
<<<

[REQUIREMENT]
UID: VEH-CM-040
REFS:
- TYPE: Parent
  VALUE: CM-040
STATEMENT: >>>
This Vehicle Connection component must satisfy requirement CM-040
<<<

[REQUIREMENT]
UID: VEH-IA-010
REFS:
- TYPE: Parent
  VALUE: IA-010
STATEMENT: >>>
This Vehicle Connection component must satisfy requirement IA-010
<<<

[REQUIREMENT]
UID: VEH-IA-020
REFS:
- TYPE: Parent
  VALUE: IA-020
STATEMENT: >>>
This Vehicle Connection component must satisfy requirement IA-020
<<<

[REQUIREMENT]
UID: VEH-IA-030
REFS:
- TYPE: Parent
  VALUE: IA-030
STATEMENT: >>>
This Vehicle Connection component must satisfy requirement IA-030
<<<

[REQUIREMENT]
UID: VEH-IR-010
REFS:
- TYPE: Parent
  VALUE: IR-010
STATEMENT: >>>
This Vehicle Connection component must satisfy requirement IR-010
<<<

[REQUIREMENT]
UID: VEH-M-010
REFS:
- TYPE: Parent
  VALUE: M-010
STATEMENT: >>>
This Vehicle Connection component must satisfy requirement M-010
<<<

[REQUIREMENT]
UID: VEH-M-040
REFS:
- TYPE: Parent
  VALUE: M-040
STATEMENT: >>>
This Vehicle Connection component must satisfy requirement M-040
<<<

[REQUIREMENT]
UID: VEH-PS-010
REFS:
- TYPE: Parent
  VALUE: PS-010
STATEMENT: >>>
This Vehicle Connection component must satisfy requirement PS-010
<<<

[REQUIREMENT]
UID: VEH-RA-010
REFS:
- TYPE: Parent
  VALUE: RA-010
STATEMENT: >>>
This Vehicle Connection component must satisfy requirement RA-010
<<<

[REQUIREMENT]
UID: VEH-RA-020
REFS:
- TYPE: Parent
  VALUE: RA-020
STATEMENT: >>>
This Vehicle Connection component must satisfy requirement RA-020
<<<

[REQUIREMENT]
UID: VEH-SAA-010
REFS:
- TYPE: Parent
  VALUE: SAA-010
STATEMENT: >>>
This Vehicle Connection component must satisfy requirement SAA-010
<<<

[REQUIREMENT]
UID: VEH-SAA-020
REFS:
- TYPE: Parent
  VALUE: SAA-020
STATEMENT: >>>
This Vehicle Connection component must satisfy requirement SAA-020
<<<

[REQUIREMENT]
UID: VEH-SAA-030
REFS:
- TYPE: Parent
  VALUE: SAA-030
STATEMENT: >>>
This Vehicle Connection component must satisfy requirement SAA-030
<<<

[REQUIREMENT]
UID: VEH-SAA-040
REFS:
- TYPE: Parent
  VALUE: SAA-040
STATEMENT: >>>
This Vehicle Connection component must satisfy requirement SAA-040
<<<

[REQUIREMENT]
UID: VEH-SAA-050
REFS:
- TYPE: Parent
  VALUE: SAA-050
STATEMENT: >>>
This Vehicle Connection component must satisfy requirement SAA-050
<<<

[REQUIREMENT]
UID: VEH-SCP-010
REFS:
- TYPE: Parent
  VALUE: SCP-010
STATEMENT: >>>
This Vehicle Connection component must satisfy requirement SCP-010
<<<

[REQUIREMENT]
UID: VEH-SCP-011
REFS:
- TYPE: Parent
  VALUE: SCP-011
STATEMENT: >>>
This Vehicle Connection component must satisfy requirement SCP-011
<<<

[REQUIREMENT]
UID: VEH-SCP-020
REFS:
- TYPE: Parent
  VALUE: SCP-020
STATEMENT: >>>
This Vehicle Connection component must satisfy requirement SCP-020
<<<

[REQUIREMENT]
UID: VEH-SCP-030
REFS:
- TYPE: Parent
  VALUE: SCP-030
STATEMENT: >>>
This Vehicle Connection component must satisfy requirement SCP-030
<<<

[REQUIREMENT]
UID: VEH-SCP-040
REFS:
- TYPE: Parent
  VALUE: SCP-040
STATEMENT: >>>
This Vehicle Connection component must satisfy requirement SCP-040
<<<

[REQUIREMENT]
UID: VEH-SCP-060
REFS:
- TYPE: Parent
  VALUE: SCP-060
STATEMENT: >>>
This Vehicle Connection component must satisfy requirement SCP-060
<<<

[REQUIREMENT]
UID: VEH-SCP-100
REFS:
- TYPE: Parent
  VALUE: SCP-100
STATEMENT: >>>
This Vehicle Connection component must satisfy requirement SCP-100
<<<

[REQUIREMENT]
UID: VEH-SCP-140
REFS:
- TYPE: Parent
  VALUE: SCP-140
STATEMENT: >>>
This Vehicle Connection component must satisfy requirement SCP-140
<<<

[REQUIREMENT]
UID: VEH-SII-010
REFS:
- TYPE: Parent
  VALUE: SII-010
STATEMENT: >>>
This Vehicle Connection component must satisfy requirement SII-010
<<<

[REQUIREMENT]
UID: VEH-SII-011
REFS:
- TYPE: Parent
  VALUE: SII-011
STATEMENT: >>>
This Vehicle Connection component must satisfy requirement SII-011
<<<

[REQUIREMENT]
UID: VEH-SII-020
REFS:
- TYPE: Parent
  VALUE: SII-020
STATEMENT: >>>
This Vehicle Connection component must satisfy requirement SII-020
<<<

[REQUIREMENT]
UID: VEH-SII-021
REFS:
- TYPE: Parent
  VALUE: SII-021
STATEMENT: >>>
This Vehicle Connection component must satisfy requirement SII-021
<<<

[REQUIREMENT]
UID: VEH-SII-030
REFS:
- TYPE: Parent
  VALUE: SII-030
STATEMENT: >>>
This Vehicle Connection component must satisfy requirement SII-030
<<<

[REQUIREMENT]
UID: VEH-SII-040
REFS:
- TYPE: Parent
  VALUE: SII-040
STATEMENT: >>>
This Vehicle Connection component must satisfy requirement SII-040
<<<

[REQUIREMENT]
UID: VEH-SII-041
REFS:
- TYPE: Parent
  VALUE: SII-041
STATEMENT: >>>
This Vehicle Connection component must satisfy requirement SII-041
<<<

[REQUIREMENT]
UID: VEH-SII-060
REFS:
- TYPE: Parent
  VALUE: SII-060
STATEMENT: >>>
This Vehicle Connection component must satisfy requirement SII-060
<<<

[REQUIREMENT]
UID: VEH-SII-070
REFS:
- TYPE: Parent
  VALUE: SII-070
STATEMENT: >>>
This Vehicle Connection component must satisfy requirement SII-070
<<<

[REQUIREMENT]
UID: VEH-SII-071
REFS:
- TYPE: Parent
  VALUE: SII-071
STATEMENT: >>>
This Vehicle Connection component must satisfy requirement SII-071
<<<

[REQUIREMENT]
UID: VEH-SII-080
REFS:
- TYPE: Parent
  VALUE: SII-080
STATEMENT: >>>
This Vehicle Connection component must satisfy requirement SII-080
<<<

[REQUIREMENT]
UID: VEH-SII-081
REFS:
- TYPE: Parent
  VALUE: SII-081
STATEMENT: >>>
This Vehicle Connection component must satisfy requirement SII-081
<<<

[REQUIREMENT]
UID: VEH-SII-090
REFS:
- TYPE: Parent
  VALUE: SII-090
STATEMENT: >>>
This Vehicle Connection component must satisfy requirement SII-090
<<<

[REQUIREMENT]
UID: VEH-SII-120
REFS:
- TYPE: Parent
  VALUE: SII-120
STATEMENT: >>>
This Vehicle Connection component must satisfy requirement SII-120
<<<

[REQUIREMENT]
UID: VEH-SII-130
REFS:
- TYPE: Parent
  VALUE: SII-130
STATEMENT: >>>
This Vehicle Connection component must satisfy requirement SII-130
<<<

[REQUIREMENT]
UID: VEH-SII-140
REFS:
- TYPE: Parent
  VALUE: SII-140
STATEMENT: >>>
This Vehicle Connection component must satisfy requirement SII-140
<<<

[REQUIREMENT]
UID: VEH-SII-150
REFS:
- TYPE: Parent
  VALUE: SII-150
STATEMENT: >>>
This Vehicle Connection component must satisfy requirement SII-150
<<<

[REQUIREMENT]
UID: VEH-SII-170
REFS:
- TYPE: Parent
  VALUE: SII-170
STATEMENT: >>>
This Vehicle Connection component must satisfy requirement SII-170
<<<

[REQUIREMENT]
UID: VEH-SII-171
REFS:
- TYPE: Parent
  VALUE: SII-171
STATEMENT: >>>
This Vehicle Connection component must satisfy requirement SII-171
<<<

[REQUIREMENT]
UID: VEH-SII-180
REFS:
- TYPE: Parent
  VALUE: SII-180
STATEMENT: >>>
This Vehicle Connection component must satisfy requirement SII-180
<<<

[REQUIREMENT]
UID: VEH-SII-200
REFS:
- TYPE: Parent
  VALUE: SII-200
STATEMENT: >>>
This Vehicle Connection component must satisfy requirement SII-200
<<<
