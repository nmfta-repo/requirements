[DOCUMENT]
TITLE: NMFTA Telematics (Connectivity or Communications Component) Security Requirements

[REQUIREMENT]
UID: COMMS-AC-010
REFS:
- TYPE: Parent
  VALUE: AC-010
STATEMENT: >>>
This Connectivity/Communications component must satisfy requirement AC-010
<<<

[REQUIREMENT]
UID: COMMS-AC-020
REFS:
- TYPE: Parent
  VALUE: AC-020
STATEMENT: >>>
This Connectivity/Communications component must satisfy requirement AC-020
<<<

[REQUIREMENT]
UID: COMMS-AC-030
REFS:
- TYPE: Parent
  VALUE: AC-030
STATEMENT: >>>
This Connectivity/Communications component must satisfy requirement AC-030
<<<

[REQUIREMENT]
UID: COMMS-AC-040
REFS:
- TYPE: Parent
  VALUE: AC-040
STATEMENT: >>>
This Connectivity/Communications component must satisfy requirement AC-040
<<<

[REQUIREMENT]
UID: COMMS-AC-041
REFS:
- TYPE: Parent
  VALUE: AC-041
STATEMENT: >>>
This Connectivity/Communications component must satisfy requirement AC-041
<<<

[REQUIREMENT]
UID: COMMS-AC-050
REFS:
- TYPE: Parent
  VALUE: AC-050
STATEMENT: >>>
This Connectivity/Communications component must satisfy requirement AC-050
<<<

[REQUIREMENT]
UID: COMMS-AC-060
REFS:
- TYPE: Parent
  VALUE: AC-060
STATEMENT: >>>
This Connectivity/Communications component must satisfy requirement AC-060
<<<

[REQUIREMENT]
UID: COMMS-AC-061
REFS:
- TYPE: Parent
  VALUE: AC-061
STATEMENT: >>>
This Connectivity/Communications component must satisfy requirement AC-061
<<<

[REQUIREMENT]
UID: COMMS-AC-062
REFS:
- TYPE: Parent
  VALUE: AC-062
STATEMENT: >>>
This Connectivity/Communications component must satisfy requirement AC-062
<<<

[REQUIREMENT]
UID: COMMS-AC-063
REFS:
- TYPE: Parent
  VALUE: AC-063
STATEMENT: >>>
This Connectivity/Communications component must satisfy requirement AC-063
<<<

[REQUIREMENT]
UID: COMMS-AC-080
REFS:
- TYPE: Parent
  VALUE: AC-080
STATEMENT: >>>
This Connectivity/Communications component must satisfy requirement AC-080
<<<

[REQUIREMENT]
UID: COMMS-CM-010
REFS:
- TYPE: Parent
  VALUE: CM-010
STATEMENT: >>>
This Connectivity/Communications component must satisfy requirement CM-010
<<<

[REQUIREMENT]
UID: COMMS-CM-020
REFS:
- TYPE: Parent
  VALUE: CM-020
STATEMENT: >>>
This Connectivity/Communications component must satisfy requirement CM-020
<<<

[REQUIREMENT]
UID: COMMS-CM-030
REFS:
- TYPE: Parent
  VALUE: CM-030
STATEMENT: >>>
This Connectivity/Communications component must satisfy requirement CM-030
<<<

[REQUIREMENT]
UID: COMMS-CM-040
REFS:
- TYPE: Parent
  VALUE: CM-040
STATEMENT: >>>
This Connectivity/Communications component must satisfy requirement CM-040
<<<

[REQUIREMENT]
UID: COMMS-IA-010
REFS:
- TYPE: Parent
  VALUE: IA-010
STATEMENT: >>>
This Connectivity/Communications component must satisfy requirement IA-010
<<<

[REQUIREMENT]
UID: COMMS-IA-020
REFS:
- TYPE: Parent
  VALUE: IA-020
STATEMENT: >>>
This Connectivity/Communications component must satisfy requirement IA-020
<<<

[REQUIREMENT]
UID: COMMS-IA-030
REFS:
- TYPE: Parent
  VALUE: IA-030
STATEMENT: >>>
This Connectivity/Communications component must satisfy requirement IA-030
<<<

[REQUIREMENT]
UID: COMMS-IR-010
REFS:
- TYPE: Parent
  VALUE: IR-010
STATEMENT: >>>
This Connectivity/Communications component must satisfy requirement IR-010
<<<

[REQUIREMENT]
UID: COMMS-M-010
REFS:
- TYPE: Parent
  VALUE: M-010
STATEMENT: >>>
This Connectivity/Communications component must satisfy requirement M-010
<<<

[REQUIREMENT]
UID: COMMS-M-040
REFS:
- TYPE: Parent
  VALUE: M-040
STATEMENT: >>>
This Connectivity/Communications component must satisfy requirement M-040
<<<

[REQUIREMENT]
UID: COMMS-PS-010
REFS:
- TYPE: Parent
  VALUE: PS-010
STATEMENT: >>>
This Connectivity/Communications component must satisfy requirement PS-010
<<<

[REQUIREMENT]
UID: COMMS-RA-010
REFS:
- TYPE: Parent
  VALUE: RA-010
STATEMENT: >>>
This Connectivity/Communications component must satisfy requirement RA-010
<<<

[REQUIREMENT]
UID: COMMS-RA-020
REFS:
- TYPE: Parent
  VALUE: RA-020
STATEMENT: >>>
This Connectivity/Communications component must satisfy requirement RA-020
<<<

[REQUIREMENT]
UID: COMMS-SAA-010
REFS:
- TYPE: Parent
  VALUE: SAA-010
STATEMENT: >>>
This Connectivity/Communications component must satisfy requirement SAA-010
<<<

[REQUIREMENT]
UID: COMMS-SAA-020
REFS:
- TYPE: Parent
  VALUE: SAA-020
STATEMENT: >>>
This Connectivity/Communications component must satisfy requirement SAA-020
<<<

[REQUIREMENT]
UID: COMMS-SAA-030
REFS:
- TYPE: Parent
  VALUE: SAA-030
STATEMENT: >>>
This Connectivity/Communications component must satisfy requirement SAA-030
<<<

[REQUIREMENT]
UID: COMMS-SAA-040
REFS:
- TYPE: Parent
  VALUE: SAA-040
STATEMENT: >>>
This Connectivity/Communications component must satisfy requirement SAA-040
<<<

[REQUIREMENT]
UID: COMMS-SAA-050
REFS:
- TYPE: Parent
  VALUE: SAA-050
STATEMENT: >>>
This Connectivity/Communications component must satisfy requirement SAA-050
<<<

[REQUIREMENT]
UID: COMMS-SCP-010
REFS:
- TYPE: Parent
  VALUE: SCP-010
STATEMENT: >>>
This Connectivity/Communications component must satisfy requirement SCP-010
<<<

[REQUIREMENT]
UID: COMMS-SCP-011
REFS:
- TYPE: Parent
  VALUE: SCP-011
STATEMENT: >>>
This Connectivity/Communications component must satisfy requirement SCP-011
<<<

[REQUIREMENT]
UID: COMMS-SCP-020
REFS:
- TYPE: Parent
  VALUE: SCP-020
STATEMENT: >>>
This Connectivity/Communications component must satisfy requirement SCP-020
<<<

[REQUIREMENT]
UID: COMMS-SCP-030
REFS:
- TYPE: Parent
  VALUE: SCP-030
STATEMENT: >>>
This Connectivity/Communications component must satisfy requirement SCP-030
<<<

[REQUIREMENT]
UID: COMMS-SCP-040
REFS:
- TYPE: Parent
  VALUE: SCP-040
STATEMENT: >>>
This Connectivity/Communications component must satisfy requirement SCP-040
<<<

[REQUIREMENT]
UID: COMMS-SCP-060
REFS:
- TYPE: Parent
  VALUE: SCP-060
STATEMENT: >>>
This Connectivity/Communications component must satisfy requirement SCP-060
<<<

[REQUIREMENT]
UID: COMMS-SCP-090
REFS:
- TYPE: Parent
  VALUE: SCP-090
STATEMENT: >>>
This Connectivity/Communications component must satisfy requirement SCP-090
<<<

[REQUIREMENT]
UID: COMMS-SCP-091
REFS:
- TYPE: Parent
  VALUE: SCP-091
STATEMENT: >>>
This Connectivity/Communications component must satisfy requirement SCP-091
<<<

[REQUIREMENT]
UID: COMMS-SCP-120
REFS:
- TYPE: Parent
  VALUE: SCP-120
STATEMENT: >>>
This Connectivity/Communications component must satisfy requirement SCP-120
<<<

[REQUIREMENT]
UID: COMMS-SCP-130
REFS:
- TYPE: Parent
  VALUE: SCP-130
STATEMENT: >>>
This Connectivity/Communications component must satisfy requirement SCP-130
<<<

[REQUIREMENT]
UID: COMMS-SCP-140
REFS:
- TYPE: Parent
  VALUE: SCP-140
STATEMENT: >>>
This Connectivity/Communications component must satisfy requirement SCP-140
<<<

[REQUIREMENT]
UID: COMMS-SII-010
REFS:
- TYPE: Parent
  VALUE: SII-010
STATEMENT: >>>
This Connectivity/Communications component must satisfy requirement SII-010
<<<

[REQUIREMENT]
UID: COMMS-SII-011
REFS:
- TYPE: Parent
  VALUE: SII-011
STATEMENT: >>>
This Connectivity/Communications component must satisfy requirement SII-011
<<<

[REQUIREMENT]
UID: COMMS-SII-020
REFS:
- TYPE: Parent
  VALUE: SII-020
STATEMENT: >>>
This Connectivity/Communications component must satisfy requirement SII-020
<<<

[REQUIREMENT]
UID: COMMS-SII-021
REFS:
- TYPE: Parent
  VALUE: SII-021
STATEMENT: >>>
This Connectivity/Communications component must satisfy requirement SII-021
<<<

[REQUIREMENT]
UID: COMMS-SII-030
REFS:
- TYPE: Parent
  VALUE: SII-030
STATEMENT: >>>
This Connectivity/Communications component must satisfy requirement SII-030
<<<

[REQUIREMENT]
UID: COMMS-SII-040
REFS:
- TYPE: Parent
  VALUE: SII-040
STATEMENT: >>>
This Connectivity/Communications component must satisfy requirement SII-040
<<<

[REQUIREMENT]
UID: COMMS-SII-041
REFS:
- TYPE: Parent
  VALUE: SII-041
STATEMENT: >>>
This Connectivity/Communications component must satisfy requirement SII-041
<<<

[REQUIREMENT]
UID: COMMS-SII-060
REFS:
- TYPE: Parent
  VALUE: SII-060
STATEMENT: >>>
This Connectivity/Communications component must satisfy requirement SII-060
<<<

[REQUIREMENT]
UID: COMMS-SII-070
REFS:
- TYPE: Parent
  VALUE: SII-070
STATEMENT: >>>
This Connectivity/Communications component must satisfy requirement SII-070
<<<

[REQUIREMENT]
UID: COMMS-SII-071
REFS:
- TYPE: Parent
  VALUE: SII-071
STATEMENT: >>>
This Connectivity/Communications component must satisfy requirement SII-071
<<<

[REQUIREMENT]
UID: COMMS-SII-080
REFS:
- TYPE: Parent
  VALUE: SII-080
STATEMENT: >>>
This Connectivity/Communications component must satisfy requirement SII-080
<<<

[REQUIREMENT]
UID: COMMS-SII-081
REFS:
- TYPE: Parent
  VALUE: SII-081
STATEMENT: >>>
This Connectivity/Communications component must satisfy requirement SII-081
<<<

[REQUIREMENT]
UID: COMMS-SII-090
REFS:
- TYPE: Parent
  VALUE: SII-090
STATEMENT: >>>
This Connectivity/Communications component must satisfy requirement SII-090
<<<

[REQUIREMENT]
UID: COMMS-SII-110
REFS:
- TYPE: Parent
  VALUE: SII-110
STATEMENT: >>>
This Connectivity/Communications component must satisfy requirement SII-110
<<<

[REQUIREMENT]
UID: COMMS-SII-120
REFS:
- TYPE: Parent
  VALUE: SII-120
STATEMENT: >>>
This Connectivity/Communications component must satisfy requirement SII-120
<<<

[REQUIREMENT]
UID: COMMS-SII-130
REFS:
- TYPE: Parent
  VALUE: SII-130
STATEMENT: >>>
This Connectivity/Communications component must satisfy requirement SII-130
<<<

[REQUIREMENT]
UID: COMMS-SII-140
REFS:
- TYPE: Parent
  VALUE: SII-140
STATEMENT: >>>
This Connectivity/Communications component must satisfy requirement SII-140
<<<

[REQUIREMENT]
UID: COMMS-SII-150
REFS:
- TYPE: Parent
  VALUE: SII-150
STATEMENT: >>>
This Connectivity/Communications component must satisfy requirement SII-150
<<<

[REQUIREMENT]
UID: COMMS-SII-170
REFS:
- TYPE: Parent
  VALUE: SII-170
STATEMENT: >>>
This Connectivity/Communications component must satisfy requirement SII-170
<<<

[REQUIREMENT]
UID: COMMS-SII-171
REFS:
- TYPE: Parent
  VALUE: SII-171
STATEMENT: >>>
This Connectivity/Communications component must satisfy requirement SII-171
<<<

[REQUIREMENT]
UID: COMMS-SII-180
REFS:
- TYPE: Parent
  VALUE: SII-180
STATEMENT: >>>
This Connectivity/Communications component must satisfy requirement SII-180
<<<

[REQUIREMENT]
UID: COMMS-SII-200
REFS:
- TYPE: Parent
  VALUE: SII-200
STATEMENT: >>>
This Connectivity/Communications component must satisfy requirement SII-200
<<<
