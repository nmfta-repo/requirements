[DOCUMENT]
TITLE: NMFTA Telematics (Cloud Component) Security Requirements

[REQUIREMENT]
UID: CLOUD-AA-010
REFS:
- TYPE: Parent
  VALUE: AA-010
STATEMENT: >>>
This Cloud or Back-end component must satisfy requirement AA-010
<<<

[REQUIREMENT]
UID: CLOUD-AC-010
REFS:
- TYPE: Parent
  VALUE: AC-010
STATEMENT: >>>
This Cloud or Back-end component must satisfy requirement AC-010
<<<

[REQUIREMENT]
UID: CLOUD-AC-030
REFS:
- TYPE: Parent
  VALUE: AC-030
STATEMENT: >>>
This Cloud or Back-end component must satisfy requirement AC-030
<<<

[REQUIREMENT]
UID: CLOUD-AC-040
REFS:
- TYPE: Parent
  VALUE: AC-040
STATEMENT: >>>
This Cloud or Back-end component must satisfy requirement AC-040
<<<

[REQUIREMENT]
UID: CLOUD-AC-041
REFS:
- TYPE: Parent
  VALUE: AC-041
STATEMENT: >>>
This Cloud or Back-end component must satisfy requirement AC-041
<<<

[REQUIREMENT]
UID: CLOUD-AC-050
REFS:
- TYPE: Parent
  VALUE: AC-050
STATEMENT: >>>
This Cloud or Back-end component must satisfy requirement AC-050
<<<

[REQUIREMENT]
UID: CLOUD-AC-070
REFS:
- TYPE: Parent
  VALUE: AC-070
STATEMENT: >>>
This Cloud or Back-end component must satisfy requirement AC-070
<<<

[REQUIREMENT]
UID: CLOUD-CM-020
REFS:
- TYPE: Parent
  VALUE: CM-020
STATEMENT: >>>
This Cloud or Back-end component must satisfy requirement CM-020
<<<

[REQUIREMENT]
UID: CLOUD-CM-030
REFS:
- TYPE: Parent
  VALUE: CM-030
STATEMENT: >>>
This Cloud or Back-end component must satisfy requirement CM-030
<<<

[REQUIREMENT]
UID: CLOUD-CM-040
REFS:
- TYPE: Parent
  VALUE: CM-040
STATEMENT: >>>
This Cloud or Back-end component must satisfy requirement CM-040
<<<

[REQUIREMENT]
UID: CLOUD-IA-010
REFS:
- TYPE: Parent
  VALUE: IA-010
STATEMENT: >>>
This Cloud or Back-end component must satisfy requirement IA-010
<<<

[REQUIREMENT]
UID: CLOUD-IA-030
REFS:
- TYPE: Parent
  VALUE: IA-030
STATEMENT: >>>
This Cloud or Back-end component must satisfy requirement IA-030
<<<

[REQUIREMENT]
UID: CLOUD-IR-010
REFS:
- TYPE: Parent
  VALUE: IR-010
STATEMENT: >>>
This Cloud or Back-end component must satisfy requirement IR-010
<<<

[REQUIREMENT]
UID: CLOUD-M-010
REFS:
- TYPE: Parent
  VALUE: M-010
STATEMENT: >>>
This Cloud or Back-end component must satisfy requirement M-010
<<<

[REQUIREMENT]
UID: CLOUD-M-020
REFS:
- TYPE: Parent
  VALUE: M-020
STATEMENT: >>>
This Cloud or Back-end component must satisfy requirement M-020
<<<

[REQUIREMENT]
UID: CLOUD-M-030
REFS:
- TYPE: Parent
  VALUE: M-030
STATEMENT: >>>
This Cloud or Back-end component must satisfy requirement M-030
<<<

[REQUIREMENT]
UID: CLOUD-M-031
REFS:
- TYPE: Parent
  VALUE: M-031
STATEMENT: >>>
This Cloud or Back-end component must satisfy requirement M-031
<<<

[REQUIREMENT]
UID: CLOUD-M-032
REFS:
- TYPE: Parent
  VALUE: M-032
STATEMENT: >>>
This Cloud or Back-end component must satisfy requirement M-032
<<<

[REQUIREMENT]
UID: CLOUD-P-010
REFS:
- TYPE: Parent
  VALUE: P-010
STATEMENT: >>>
This Cloud or Back-end component must satisfy requirement P-010
<<<

[REQUIREMENT]
UID: CLOUD-P-020
REFS:
- TYPE: Parent
  VALUE: P-020
STATEMENT: >>>
This Cloud or Back-end component must satisfy requirement P-020
<<<

[REQUIREMENT]
UID: CLOUD-P-030
REFS:
- TYPE: Parent
  VALUE: P-030
STATEMENT: >>>
This Cloud or Back-end component must satisfy requirement P-030
<<<

[REQUIREMENT]
UID: CLOUD-PS-010
REFS:
- TYPE: Parent
  VALUE: PS-010
STATEMENT: >>>
This Cloud or Back-end component must satisfy requirement PS-010
<<<

[REQUIREMENT]
UID: CLOUD-RA-010
REFS:
- TYPE: Parent
  VALUE: RA-010
STATEMENT: >>>
This Cloud or Back-end component must satisfy requirement RA-010
<<<

[REQUIREMENT]
UID: CLOUD-RA-020
REFS:
- TYPE: Parent
  VALUE: RA-020
STATEMENT: >>>
This Cloud or Back-end component must satisfy requirement RA-020
<<<

[REQUIREMENT]
UID: CLOUD-SAA-010
REFS:
- TYPE: Parent
  VALUE: SAA-010
STATEMENT: >>>
This Cloud or Back-end component must satisfy requirement SAA-010
<<<

[REQUIREMENT]
UID: CLOUD-SAA-020
REFS:
- TYPE: Parent
  VALUE: SAA-020
STATEMENT: >>>
This Cloud or Back-end component must satisfy requirement SAA-020
<<<

[REQUIREMENT]
UID: CLOUD-SAA-030
REFS:
- TYPE: Parent
  VALUE: SAA-030
STATEMENT: >>>
This Cloud or Back-end component must satisfy requirement SAA-030
<<<

[REQUIREMENT]
UID: CLOUD-SAA-040
REFS:
- TYPE: Parent
  VALUE: SAA-040
STATEMENT: >>>
This Cloud or Back-end component must satisfy requirement SAA-040
<<<

[REQUIREMENT]
UID: CLOUD-SAA-050
REFS:
- TYPE: Parent
  VALUE: SAA-050
STATEMENT: >>>
This Cloud or Back-end component must satisfy requirement SAA-050
<<<

[REQUIREMENT]
UID: CLOUD-SCP-010
REFS:
- TYPE: Parent
  VALUE: SCP-010
STATEMENT: >>>
This Cloud or Back-end component must satisfy requirement SCP-010
<<<

[REQUIREMENT]
UID: CLOUD-SCP-011
REFS:
- TYPE: Parent
  VALUE: SCP-011
STATEMENT: >>>
This Cloud or Back-end component must satisfy requirement SCP-011
<<<

[REQUIREMENT]
UID: CLOUD-SCP-020
REFS:
- TYPE: Parent
  VALUE: SCP-020
STATEMENT: >>>
This Cloud or Back-end component must satisfy requirement SCP-020
<<<

[REQUIREMENT]
UID: CLOUD-SCP-030
REFS:
- TYPE: Parent
  VALUE: SCP-030
STATEMENT: >>>
This Cloud or Back-end component must satisfy requirement SCP-030
<<<

[REQUIREMENT]
UID: CLOUD-SCP-040
REFS:
- TYPE: Parent
  VALUE: SCP-040
STATEMENT: >>>
This Cloud or Back-end component must satisfy requirement SCP-040
<<<

[REQUIREMENT]
UID: CLOUD-SCP-050
REFS:
- TYPE: Parent
  VALUE: SCP-050
STATEMENT: >>>
This Cloud or Back-end component must satisfy requirement SCP-050
<<<

[REQUIREMENT]
UID: CLOUD-SCP-090
REFS:
- TYPE: Parent
  VALUE: SCP-090
STATEMENT: >>>
This Cloud or Back-end component must satisfy requirement SCP-090
<<<

[REQUIREMENT]
UID: CLOUD-SCP-091
REFS:
- TYPE: Parent
  VALUE: SCP-091
STATEMENT: >>>
This Cloud or Back-end component must satisfy requirement SCP-091
<<<

[REQUIREMENT]
UID: CLOUD-SCP-092
REFS:
- TYPE: Parent
  VALUE: SCP-092
STATEMENT: >>>
This Cloud or Back-end component must satisfy requirement SCP-092
<<<

[REQUIREMENT]
UID: CLOUD-SCP-110
REFS:
- TYPE: Parent
  VALUE: SCP-110
STATEMENT: >>>
This Cloud or Back-end component must satisfy requirement SCP-110
<<<

[REQUIREMENT]
UID: CLOUD-SCP-120
REFS:
- TYPE: Parent
  VALUE: SCP-120
STATEMENT: >>>
This Cloud or Back-end component must satisfy requirement SCP-120
<<<

[REQUIREMENT]
UID: CLOUD-SCP-130
REFS:
- TYPE: Parent
  VALUE: SCP-130
STATEMENT: >>>
This Cloud or Back-end component must satisfy requirement SCP-130
<<<

[REQUIREMENT]
UID: CLOUD-SII-010
REFS:
- TYPE: Parent
  VALUE: SII-010
STATEMENT: >>>
This Cloud or Back-end component must satisfy requirement SII-010
<<<

[REQUIREMENT]
UID: CLOUD-SII-011
REFS:
- TYPE: Parent
  VALUE: SII-011
STATEMENT: >>>
This Cloud or Back-end component must satisfy requirement SII-011
<<<

[REQUIREMENT]
UID: CLOUD-SII-020
REFS:
- TYPE: Parent
  VALUE: SII-020
STATEMENT: >>>
This Cloud or Back-end component must satisfy requirement SII-020
<<<

[REQUIREMENT]
UID: CLOUD-SII-021
REFS:
- TYPE: Parent
  VALUE: SII-021
STATEMENT: >>>
This Cloud or Back-end component must satisfy requirement SII-021
<<<

[REQUIREMENT]
UID: CLOUD-SII-070
REFS:
- TYPE: Parent
  VALUE: SII-070
STATEMENT: >>>
This Cloud or Back-end component must satisfy requirement SII-070
<<<

[REQUIREMENT]
UID: CLOUD-SII-071
REFS:
- TYPE: Parent
  VALUE: SII-071
STATEMENT: >>>
This Cloud or Back-end component must satisfy requirement SII-071
<<<

[REQUIREMENT]
UID: CLOUD-SII-080
REFS:
- TYPE: Parent
  VALUE: SII-080
STATEMENT: >>>
This Cloud or Back-end component must satisfy requirement SII-080
<<<

[REQUIREMENT]
UID: CLOUD-SII-081
REFS:
- TYPE: Parent
  VALUE: SII-081
STATEMENT: >>>
This Cloud or Back-end component must satisfy requirement SII-081
<<<

[REQUIREMENT]
UID: CLOUD-SII-090
REFS:
- TYPE: Parent
  VALUE: SII-090
STATEMENT: >>>
This Cloud or Back-end component must satisfy requirement SII-090
<<<

[REQUIREMENT]
UID: CLOUD-SII-100
REFS:
- TYPE: Parent
  VALUE: SII-100
STATEMENT: >>>
This Cloud or Back-end component must satisfy requirement SII-100
<<<

[REQUIREMENT]
UID: CLOUD-SII-110
REFS:
- TYPE: Parent
  VALUE: SII-110
STATEMENT: >>>
This Cloud or Back-end component must satisfy requirement SII-110
<<<

[REQUIREMENT]
UID: CLOUD-SII-120
REFS:
- TYPE: Parent
  VALUE: SII-120
STATEMENT: >>>
This Cloud or Back-end component must satisfy requirement SII-120
<<<

[REQUIREMENT]
UID: CLOUD-SII-130
REFS:
- TYPE: Parent
  VALUE: SII-130
STATEMENT: >>>
This Cloud or Back-end component must satisfy requirement SII-130
<<<

[REQUIREMENT]
UID: CLOUD-SII-140
REFS:
- TYPE: Parent
  VALUE: SII-140
STATEMENT: >>>
This Cloud or Back-end component must satisfy requirement SII-140
<<<

[REQUIREMENT]
UID: CLOUD-SII-150
REFS:
- TYPE: Parent
  VALUE: SII-150
STATEMENT: >>>
This Cloud or Back-end component must satisfy requirement SII-150
<<<

[REQUIREMENT]
UID: CLOUD-SII-170
REFS:
- TYPE: Parent
  VALUE: SII-170
STATEMENT: >>>
This Cloud or Back-end component must satisfy requirement SII-170
<<<

[REQUIREMENT]
UID: CLOUD-SII-171
REFS:
- TYPE: Parent
  VALUE: SII-171
STATEMENT: >>>
This Cloud or Back-end component must satisfy requirement SII-171
<<<

[REQUIREMENT]
UID: CLOUD-SII-180
REFS:
- TYPE: Parent
  VALUE: SII-180
STATEMENT: >>>
This Cloud or Back-end component must satisfy requirement SII-180
<<<

[REQUIREMENT]
UID: CLOUD-SII-200
REFS:
- TYPE: Parent
  VALUE: SII-200
STATEMENT: >>>
This Cloud or Back-end component must satisfy requirement SII-200
<<<
